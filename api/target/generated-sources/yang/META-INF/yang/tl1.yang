module tl1 {
    yang-version 1;
    namespace "urn:opendaylight:params:xml:ns:yang:tl1";
    prefix "tl1";

    revision "2015-01-05" {
        description "Initial revision of tl1 model";
    }
    rpc hello-tl1 {
        input {
            leaf name {
                type string;
            }
        }
        output {
            leaf greeting {
                type string;
            }
        }
    }
    notification Device{
    	leaf deviceStatu{
    		type enumeration{
    			enum "working"{
    				value 0;
    				description "the device is working properly";
    			}
    			enum "not_working"{
    				value 1;
    				description "the device is not working properly";
    			}
    		}
    	}
    }
}
